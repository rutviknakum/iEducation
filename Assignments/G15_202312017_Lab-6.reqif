# Specification Title

# Specification: Specification Document
- Description: Requirements Document

## REQ-1: USER AUTHENTICATION
- OWNER: ADMIN

### REQ-1.1: LOGIN
Admins should be able to authenticate their credentials against the database securely.

### REQ-1.2: LOGIN FAILURE
Incorrect credentials should result in an appropriate error message.

## REQ-2: FORGOT PASSWORD
Admins should receive an email with instructions to reset their password.
- OWNER: ADMIN

## REQ-3: MANAGE STUDENTS
Admins should have the ability to add, edit, or delete student records.
- OWNER: ADMIN

## REQ-4: TIMETABLE
- OWNER: ADMIN

### REQ-4.1: MANAGE TIMETABLE
Admins should be able to view, add, and update course timetables.

#### REQ-4.1.1: TIMETABLE DETAILS
Timetable details should include course name, subject, date, and time.

## REQ-5: NOTICE
Admins should be able to specify the visibility of notices to relevant recipients.
- OWNER: ADMIN

### REQ-5.1: NOTICE DETAILS
Notices should be categorized by topics such as cultural festivals, college activities, sports, exams, job vacancies, and general updates.

## REQ-6: MATERIAL
- OWNER: ADMIN

### REQ-6.1: MATERIAL UPLOAD
Admins should be able to upload and share study materials.

### REQ-6.2: MATERIAL CATEGORIZE
Admins should categorize materials by subject name, stream, semester, and date/time for easy access by students.

### REQ-6.3: MATERIAL DETAILS
Study materials should include lecture notes, presentations, and assignments.

## REQ-7: MANAGE COURSE
Admins should have the ability to add new courses, update existing ones, or deactivate courses that are no longer offered.
- OWNER: ADMIN

## REQ-8: MANAGE ATTENDANCE
Admins should have access to a dashboard showing attendance statistics for each student.
- OWNER: ADMIN

## REQ-9: MANAGE LEAVE REQUESTS
Admins should receive notifications of leave requests and have the ability to approve or reject them.
- OWNER: ADMIN

## REQ-10: MANAGE RESULTS
- OWNER: ADMIN

### REQ-10.1: PUBLISH RESULTS
Admins should be able to publish examination results for all courses.

### REQ-10.2: ACCURATE RESULTS
Admins should ensure the accuracy and security of examination results.

## REQ-11: MANAGE STAFF
- OWNER: ADMIN

### REQ-11.1: ACCESS STAFF DETAILS
Admins should have access to staff details including contact information and department details.

### REQ-11.2: DELETE STAFF
Admins should be able to remove staff who have left the university

## REQ-12: MANAGE BOOK LOG
Admins should have access to a log of which student has issued which book.
- OWNER: ADMIN

## REQ-13: MANAGE FEES DETAILS
Admins should see details of students who have paid fees, mode of payment, and remaining fees for each student.
- OWNER: ADMIN

## REQ-14: LOGOUT
Admins should have a logout option to secure their account and ensure privacy.
- OWNER: ADMIN

## REQ-15: REGISTER
Students should enter personal details and receive confirmation for successful registration.
- OWNER: STUDENT

## REQ-16: LOGIN
Students should use their credentials to log in securely.
- OWNER: STUDENT

## REQ-17: FORGOT PASSWORD
Students should be able to reset their password through an email verification process.
- OWNER: STUDENT

## REQ-18: PROFILE UPDATE
Students should have access to update their personal information.
- OWNER: STUDENT

## REQ-19: LEAVE APPLICATION
Students should submit leave requests through the system for approval.
- OWNER: STUDENT

## REQ-20: VIEW ATTENDACE
Students should have access to their attendance statistics
- OWNER: STUDENT

## REQ-21: SUBMIT WORK DONE
Students should access homework details and submit completed assignments.
- OWNER: STUDENT

## REQ-22: PAY FEES
Students should see their fee status and have the option to pay dues securely.
- OWNER: STUDENT

## REQ-23: PAY LIBRARY FINE
Students should have access to view and pay library fines
- OWNER: STUDENT

## REQ-24: VIEW TIMETABLE
Students should view their timetable for classes.
- OWNER: STUDENT

## REQ-25: VIEW EXAM RESULTS
Students should view their exam results securely.
- OWNER: STUDENT

## REQ-26: VIEW SEATING PLAN
Students should be able to access the examination seating plan.
- OWNER: STUDENT

## REQ-27: VIEW TECAHER INFORMATION
Students should be able to view the list of teachers associated with their courses.
- OWNER: STUDENT

## REQ-28: ACCESS MATERIAL
Students should access lecture notes, presentations, and readings for their courses.
- OWNER: STUDENT

## REQ-29: VIEW NOTICE
Students should be able to view announcements and important notices.
- OWNER: STUDENT
